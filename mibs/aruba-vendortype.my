-- ArubaOS 7.3.2.2_44718
ARUBA-VENDORTYPE DEFINITIONS ::= BEGIN

IMPORTS
    MODULE-IDENTITY 
        FROM SNMPv2-SMI
    arubaMIBModules 
        FROM ARUBA-MIB;

arubaVendorTypeMIB    MODULE-IDENTITY
    LAST-UPDATED "201208270000Z" -- 27th August, 2012
    ORGANIZATION "Aruba Wireless Networks"
    CONTACT-INFO
       "Postal:    1322 Crossman Avenue
                    Sunnyvale, CA 94089
        E-mail:     dl-support@arubanetworks.com
        Phone:      +1 408 227 4500"
    DESCRIPTION
        "This module describes the object identifiers that are assigned to
        various components on aruba products."
    REVISION "201208270000Z"
    DESCRIPTION
        "The initial revision of vendortype-oid MIB."
    ::= {  arubaMIBModules 1 }
        
arubaVendorTypeMIBObjects OBJECT IDENTIFIER ::= { arubaVendorTypeMIB 1 }

arubaSystem OBJECT IDENTIFIER ::= { arubaVendorTypeMIBObjects 1 }

aSystemUnknown  OBJECT IDENTIFIER ::= { arubaSystem 1 }
aSystemChassis  OBJECT IDENTIFIER ::= { arubaSystem 2 }
aSystemBackplane    OBJECT IDENTIFIER ::= { arubaSystem 3 }
aSystemModule   OBJECT IDENTIFIER ::= { arubaSystem 4 }
aSystemPSU      OBJECT IDENTIFIER ::= { arubaSystem 5 }
aSystemFAN      OBJECT IDENTIFIER ::= { arubaSystem 6 }
aSystemContainer    OBJECT IDENTIFIER ::= { arubaSystem 7 }
aSystemPort     OBJECT IDENTIFIER ::= { arubaSystem 8 }
aSystemSensor   OBJECT IDENTIFIER ::= { arubaSystem 9 }

END
